module module-C3 {
  yang-version 1.1;

  namespace
    "urn:ietf:params:xml:ns:yang:module-C3";
  prefix "vC3";

  import ietf-yang-structure-ext {
    prefix sx;
  }

  import module-A3 {
    prefix "vA3";
  }

  organization "Not very";

  contact "WG Web:   <http://tools.ietf.org/wg/anima/>";
  description "This is module C3";

  revision "2022-11-13" { description "Initial version";
    reference "RFC 8366: Voucher Profile for Bootstrapping Protocols";
  }

  sx:structure module-C-things {
    uses module-C;
  }

  grouping module-C {
    description "A module C structure";
    container module-C {
      description "A wrapper container for the module-C things";
      uses vA3:module-A-contents;
      uses module-C-contents;
    }
  }

  grouping module-C-contents {
    leaf attribute-C-Gamma {
      type binary;
      description "GammaThree";
    }
  }

}
