module module-B {
  yang-version 1.1;

  namespace
    "urn:ietf:params:xml:ns:yang:module-B";
  prefix "vB";

  import ietf-restconf {
    prefix rc;
    description "restconf";
    reference "RFC8040: RESTCONF";
  }

  import module-A {
    prefix "vA";
  }

  organization "Not very";

  contact "WG Web:   <http://tools.ietf.org/wg/anima/>";
  description "This is module B";

  revision "2022-11-13" { description "Initial version";
    reference "RFC 8366: Voucher Profile for Bootstrapping Protocols";
  }

  rc:yang-data module-B-artifact {
    // YANG data template for a voucher.
    uses module-B-grouping;
  }

  grouping module-B-grouping {
    description "Grouping for module B";
    container module-B-things {
      uses vA:module-A-grouping;
      leaf attribute-B-Alpha {
        type binary;
        description "Beta";
      }
    }
  }

}
