module module-C2 {
  yang-version 1.1;

  namespace
    "urn:ietf:params:xml:ns:yang:module-C2";
  prefix "vC2";

  import ietf-restconf {
    prefix rc;
    description "restconf";
    reference "RFC8040: RESTCONF";
  }

  import module-A {
    prefix "vA";
  }

  organization "Not very";

  contact "WG Web:   <http://tools.ietf.org/wg/anima/>";
  description "This is module C2";

  revision "2022-11-13" { description "Initial version";
    reference "RFC 8366: Voucher Profile for Bootstrapping Protocols";
  }

  rc:yang-data module-C2-artifact {
    // YANG data template for a voucher.
    uses module-C2-grouping;
  }

  grouping module-C2-grouping {
    description "Grouping for module C";

    uses vA:module-A-grouping {

      augment "module-A-things" {
        leaf attribute-C-Gamma {
          type binary;
          description "GammaTwo";
        }
      }
    }
  }

}
