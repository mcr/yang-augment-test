module module-D1 {
  yang-version 1.1;

  namespace
    "urn:ietf:params:xml:ns:yang:module-D1";
  prefix "vD1";

  import ietf-restconf {
    prefix rc;
    description "restconf";
    reference "RFC8040: RESTCONF";
  }

  import module-A {
    prefix "vA";
  }

  import module-B {
    prefix "vB";
  }

  import module-C1 {
    prefix "vC1";
  }

  organization "Not very";

  contact "WG Web:   <http://tools.ietf.org/wg/anima/>";
  description "This is module D1";

  revision "2022-11-13" { description "Initial version";
    reference "RFC 8366: Voucher Profile for Bootstrapping Protocols";
  }

  rc:yang-data module-D1-artifact {
    // YANG data template for a voucher.
    uses module-D1-grouping;
  }

  grouping module-D1-grouping {
    description "Grouping for module D1";
    container module-D1-things {
      uses vA:module-A-grouping;
      uses vB:module-B-grouping;
      uses vC1:module-C1-grouping;
      leaf attribute-D-Delta {
        type binary;
        description "Delta";
      }
    }
  }

}
