module module-A {
  yang-version 1.1;

  namespace
    "urn:ietf:params:xml:ns:yang:module-A";
  prefix "vA";

  import ietf-restconf {
    prefix rc;
    description "restconf";
    reference "RFC8040: RESTCONF";
  }

  organization "Not very";

  contact "WG Web:   <http://tools.ietf.org/wg/anima/>";
  description "This is module A";

  revision "2022-11-13" { description "Initial version";
    reference "RFC 8366: Voucher Profile for Bootstrapping Protocols";
  }

  rc:yang-data module-A-artifact {
    // YANG data template for a voucher.
    uses module-A-grouping;
  }

  grouping module-A-grouping {
    description "Grouping for module A";
    container module-A-things {
      leaf attribute-A-Alpha {
        type binary;
        description "Alpha";
      }
    }
  }

}
